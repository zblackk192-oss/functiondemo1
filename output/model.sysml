package VehicleSystem {

part def F001 {
}
part def F002 {
}
part def F003 {
}
part def F004 {
}
part def F005 {
}
part def F006 {
}
part def F007 {
}
part def F008 {
}

flow F001 to F002;
flow F001 to F003;
flow F001 to F004;
flow F001 to F005;
flow F001 to F007;
flow F003 to F007;
flow F005 to F002;
flow F005 to F004;
flow F006 to F002;
flow F006 to F004;
flow F006 to F007;
flow F008 to F002;
flow F008 to F005;
flow F008 to F007;
}
